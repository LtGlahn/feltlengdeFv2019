FME workspace lagfeltstrekning.fmw

Parameters:
- SourceDataset_OGCGEOPACKAGE = $(FME_MF_DIR)feltstrekning.gpkg   # GeoPackage File
- SourceDataset_OGCGEOPACKAGE_3 = $(FME_MF_DIR)vegnett_2019_07_01.gpkg   # GeoPackage File
- DestDataset_OGCGEOPACKAGE = $(FME_MF_DIR)junk__feltstrekning.gpkg   # GeoPackage File
- SourceDataset_CSV2 = $(FME_MF_DIR)41_ferjeoppstillingsplass-eksport.csv   # Source CSV (Comma Separated Value) File(s)
- SourceDataset_FILEGDB = C:\DATA\kartverket\Basisdata_0000_Norge_25833_Fylker2019_FGDB\Basisdata_0000_Norge_25833_Fylker2019_FGDB.gdb   # File Geodatabase
- DestDataset_XLSXW = $(FME_MF_DIR)feltlengder_fylkesveg_per2019.xlsx   # Destination Microsoft Excel File

Readers:
- OGCGEOPACKAGE_1: OGCGEOPACKAGE from $(SourceDataset_OGCGEOPACKAGE)
- OGCGEOPACKAGE_2: OGCGEOPACKAGE from $(SourceDataset_OGCGEOPACKAGE_3)
- CSV2_1: CSV2 from $(SourceDataset_CSV2)
- FILEGDB_2: FILEGDB from $(SourceDataset_FILEGDB)

Writers:
- OGCGEOPACKAGE_3: OGCGEOPACKAGE to $(DestDataset_OGCGEOPACKAGE)
- XLSXW_1: XLSXW to $(DestDataset_XLSXW)

CSV (reader CSV2_1)
    attributes: VEGOBJEKT-ID uint32, TYPE-ID uint32, VERSJON uint32, FØRSTE FOREKOMST uint32, STARTDATO date, SLUTTDATO varchar(1), SIST MODIFISERT varchar(20), FERJE TIL varchar(47), ANTALL OPPSTILLINGSFELT (STK) uint32, LENGDE OPPSTILLINGSFELT, FORFLYTNINGSHEMMEDE (M) uint32, LENGDE OPPSTILLINGSFELT, TUNGE KJØRETØY (M) uint32, LENGDE OPPSTILLINGSFELT, PERSONBIL/KOMBINERT (M) uint32, ANTALL OPPSTILLINGSPL. SMÅ KJT. (STK) uint32, AREAL (M2) uint32, ETABLERINGSÅR uint32, TILLEGGSINFORMASJON varchar(53), PROSJEKTREFERANSE varchar(39), PROSJEKTINTERNOBJEKT_ID varchar(1), EIER varchar(23), VEDLIKEHOLDSANSVARLIG varchar(17), GEOMETRI, PUNKT varchar(66), UTGÅR_GEOMETRI, LINJE varchar(67), GEOMETRI, FLATE varchar(4152), UTGÅR_HAR PARKERINGSPLASS varchar(4), LOK.KOMMUNE varchar(20), LOK.KOMMUNENUMMER uint32, LOK.FYLKE varchar(17), LOK.FYLKESNUMMER uint32, LOK.RIKSVEGRUTE varchar(1), LOK.KONTRAKTSOMRÅDE varchar(545),
      LOK.VEGSYSTEMREFERANSE varchar(26), LOK.VEGKATEGORI varchar(10), LOK.FASE varchar(13), LOK.VEGNUMMER uint32, LOK.STREKNING uint32, LOK.DELSTREKNING uint32, FRA METER real64, TIL METER real64, VEGLENKESEKVENSID uint32, STARTPOSISJON real64, SLUTTPOSISJON real64, STREKNING.RETNING varchar(8), SIDEPOSISJON varchar(6), KJØREFELT uint32, TYPEVEG varchar(14), LENGDE uint32, MOR varchar(14), BARN varchar(14), GEOMETRI varchar(40)
    -> GeometryReplacer
GeometryReplacer
    KIND_LONG = OGC Well Known Text
    OGC_WKT_PRECISION_DISPLAY = 64-bit
    REMOVE_ATTRIBUTE = No
    SOURCE = @Value(GEOMETRI)
    -> CoordinateSystemSetter
CoordinateSystemSetter
    COORDSYS = EPSG:25833
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(LENGDE OPPSTILLINGSFELT, FORFLYTNINGSHEMMEDE (M)) > 0",lengde HC felt,"BOOL_OP,OR,COMPOSITE_TEST,""""""1"""""",TEST_CLAUSE,TEST @Value(LENGDE OPPSTILLINGSFELT, PERSONBIL/KOMBINERT (M)) > 0",lengde personbil,"BOOL_OP,OR,COMPOSITE_TEST,""""""1"""""",TEST_CLAUSE,TEST @Value(LENGDE OPPSTILLINGSFELT, TUNGE KJØRETØY (M)) > 0",lenge tunge kjt
    lengde HC felt -> NullAttributeMapper
    lengde personbil -> NullAttributeMapper
    lenge tunge kjt -> NullAttributeMapper
    <UNFILTERED> -> AttributeKeeper_5
NullAttributeMapper
    ATTRCHOICE = Selected Attributes
    ATTRLIST = LENGDE OPPSTILLINGSFELT, FORFLYTNINGSHEMMEDE (M) LENGDE OPPSTILLINGSFELT, PERSONBIL/KOMBINERT (M) LENGDE OPPSTILLINGSFELT, TUNGE KJØRETØY (M)
    NEW_VALUE = 0
    NULL_TREATMENT = New Value
    SOURCE_ATTR_VAL = Null
    -> ExpressionEvaluator_2
ExpressionEvaluator_2
    ACTION = Create New Attribute
    EXPRESSION = @Value(LENGDE OPPSTILLINGSFELT, FORFLYTNINGSHEMMEDE (M))+@Value(LENGDE OPPSTILLINGSFELT, PERSONBIL/KOMBINERT (M))+@Value(LENGDE OPPSTILLINGSFELT, TUNGE KJØRETØY (M))
    VAL_ATTR = sumLengdeOppstillingsfelt
    -> AttributeKeeper_5
AttributeKeeper_5
    CREATE_BULK_MODE_FEATURES = NO
    KEEP_ATTRS = ANTALL OPPSTILLINGSFELT (STK),ANTALL OPPSTILLINGSPL. SMÅ KJT. (STK),LENGDE,LENGDE OPPSTILLINGSFELT, FORFLYTNINGSHEMMEDE (M),LENGDE OPPSTILLINGSFELT, PERSONBIL/KOMBINERT (M),LENGDE OPPSTILLINGSFELT, TUNGE KJØRETØY (M),VEGLENKESEKVENSID,VEGOBJEKT-ID,VERSJON,sumLengdeOppstillingsfelt
    -> SpatialRelator [Requestor]
administrativenhetnavn (reader FILEGDB_2)
    attributes: OBJECTID objectid, objtype text(255), navn text(255), rekkefolge int, sprak text(3), fylke_fk int
    -> Tester_2
Tester_2
    BOOL_OP = OR
    TEST_CLAUSE = TEST @Value(sprak) = nor
    TEST_MODE = TEST
    PASSED -> AttributeKeeper_3
AttributeKeeper_3
    CREATE_BULK_MODE_FEATURES = NO
    KEEP_ATTRS = fylke_fk,navn
    -> FeatureMerger_3 [SUPPLIER]
vegnett_2019_07_01 (reader OGCGEOPACKAGE_2)
    attributes: href text, veglenkesekvensid int, startposisjon double, sluttposisjon double, kortform text, veglenkenummer int, segmentnummer int, startnode text, sluttnode text, referanse text, type text, detaljnivå text, typeVeg text, typeVeg_sosi text, målemetode text, feltoversikt text, geometri text, lengde double, fylke int, kommune int, vegsystemreferanse text, gate text, startdato text, sluttdato text, vref text, vegkategori text, fase text, nummer double, måledato text, medium text,
      strekning double, delstrekning double, fra_meter double, til_meter double, trafikantgruppe text, adskilte_lop text, ankerpunktmeter double, sideanleggsdel double, kryssdel double, fid int,PrimaryKey
    -> TestFilter
TestFilter
    DEFAULT_VALUE = <UNFILTERED>
    PASSED_TEST_GROUP_OUTPUT = FIRST
    TEST_LIST:
      "BOOL_OP,OR,COMPOSITE_TEST,""""""1"""""",TEST_CLAUSE,TEST @Value(vegkategori) != F",@Value(vegkategori) != F,"BOOL_OP,OR,COMPOSITE_TEST,""""""1"""""",TEST_CLAUSE,TEST @Value(fase) != V",@Value(fase) != V,"BOOL_OP,OR,COMPOSITE_TEST,""""""1"""""",TEST_CLAUSE,TEST @Value(trafikantgruppe) = G",@Value(trafikantgruppe) = G,"BOOL_OP,OR,COMPOSITE_TEST,""""""1 OR 2 OR 3 OR 4 OR 5 OR 6"""""",TEST_CLAUSE,TEST @Value(typeVeg) = Gang- og sykkelveg
      TEST @Value(typeVeg) = Sykkelveg
      TEST @Value(typeVeg) = Gangfelt
      TEST @Value(typeVeg) = Gangveg
      TEST @Value(typeVeg) = Fortau
      TEST @Value(typeVeg) = Trapp",@Value(typeVeg) = For gående og syklende
    <UNFILTERED> -> AttributeKeeper
    <UNFILTERED> -> DuplicateFilter_2
DuplicateFilter_2
    INPUT_ORDERED_CHOICE = No
    KEYATTR = typeVeg
AttributeKeeper
    CREATE_BULK_MODE_FEATURES = NO
    KEEP_ATTRS = nummer,referanse,sluttposisjon,startposisjon,type,typeVeg,vegkategori,veglenkesekvensid,vref,feltoversikt,trafikantgruppe
    -> Tester
Tester
    BOOL_OP = OR
    TEST_CLAUSE = TEST @Value(type) = KONNEKTERING
    TEST_MODE = TEST
    PASSED -> Counter
    FAILED -> Junction
    FAILED -> AttributeCreator_4
Counter
    CNT_ATTR = _count
    DOMAIN = counter
    SCOPE = Global
    START = 0
    -> InlineQuerier [konnekteringslenker]
Junction
    -> AttributeSplitter_4
fylke (reader FILEGDB_2)
    attributes: OBJECTID objectid, objid int, objtype text(32), samiskforvaltningsomrade smallint, lokalid text(100), navnerom text(100), versjonid text(100), datafangstdato date, oppdateringsdato date, datauttaksdato date, opphav text(255), fylkesnummer text(2), SHAPE_Length double, SHAPE_Area double
    -> FeatureMerger_3 [REQUESTOR]
FeatureMerger_3
    ATTR_ACCUM_MODE = Merge Supplier
    ATTR_CONFLICT_RES = Use Requestor
    IGNORE_NULLS = No
    JOIN_KEYS = @Value(objid) @Value(fylke_fk) AUTO
    MERGE_TYPE = Attributes Only
    PROCESS_DUPS = NO
    REJECT_NULL_MISSING_KEYS = No
    SUPPLIERS_FIRST = No
    MERGED -> AttributeKeeper_4
AttributeKeeper_4
    CREATE_BULK_MODE_FEATURES = NO
    KEEP_ATTRS = fylkesnummer,navn
    -> Clipper [CLIPPER]
    -> AttributeRenamer_3
AttributeRenamer_3
    ATTR_TABLE = RENAME_SET_DEFAULT navn > fylkesnavn
    MISSING_INPUT_ATTRS = REMOVE
    -> SpatialRelator [Supplier]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = WITHIN
    SUCCESS_ATTR = _related_suppliers
    -> NullAttributeMapper_2
NullAttributeMapper_2
    ATTRCHOICE = Selected Attributes
    ATTRLIST = sumLengdeOppstillingsfelt
    NEW_VALUE = 0
    NULL_TREATMENT = New Value
    SOURCE_ATTR_VAL = Null Empty "Missing (Selected Attributes Only)"
    -> StatisticsCalculator_2
    -> StatisticsCalculator_3
StatisticsCalculator_3
    CALCULATION_MODE = NUMERIC
    FEAT_STATS = sumLengdeOppstillingsfelt,NUMERIC_MODE,,,COUNT,SUM,,,,,,,,,
    SUMMARY -> StatisticsCalculator_3_Summary
StatisticsCalculator_3_Summary: Inspector
StatisticsCalculator_2
    CALCULATION_MODE = NUMERIC
    FEAT_STATS = sumLengdeOppstillingsfelt,NUMERIC_MODE,,,COUNT,SUM,,,,,,,,,
    GROUP_BY = fylkesnavn fylkesnummer
    SUMMARY -> ExpressionEvaluator_3
ExpressionEvaluator_3
    ACTION = Create New Attribute
    EXPRESSION = @Value(sumLengdeOppstillingsfelt.sum)/1000
    VAL_ATTR = sumLengdeOppstillingsfelt.sum
    -> SpatialRelator_Output
SpatialRelator_Output: Inspector
feltstrekning (reader OGCGEOPACKAGE_1)
    attributes: objekttype int, nvdbId int, versjon int, startdato text, sluttdato text, Feltoversikt i veglenkeretning text, vegsystemreferanser text, stedfestinger text, stedfesting_detaljer text, strekningslengde double, Feltoversikt i metreringsretning text, fid int,PrimaryKey
    -> DuplicateFilter
DuplicateFilter
    INPUT_ORDERED_CHOICE = No
    KEYATTR = nvdbId Feltoversikt i veglenkeretning
    UNIQUE -> AttributeSplitter
AttributeSplitter
    ATTR_NAME = stedfestinger
    DELIMITER = ,
    DROP_EMPTY_PARTS = No
    LIST_NAME = _stedfestinger
    TRIM_OPTION = Both
    -> ListExploder
ListExploder
    ATTR_ACCUM_MODE = Merge List Attributes
    ATTR_CONFLICT_RES = Use List Attribute Values
    INDEX_ATTR = _element_index
    LIST_ATTR = _stedfestinger{}
    ELEMENTS -> AttributeSplitter_2
AttributeSplitter_2
    ATTR_NAME = _stedfestinger
    DELIMITER = @
    DROP_EMPTY_PARTS = No
    LIST_NAME = _stedfestingsplitt
    TRIM_OPTION = Both
    -> AttributeSplitter_3
AttributeSplitter_3
    ATTR_NAME = _stedfestingsplitt{0}
    DELIMITER = -
    DROP_EMPTY_PARTS = No
    LIST_NAME = _posisjoner
    TRIM_OPTION = Both
    -> AttributeCreator
AttributeCreator
    ATTR_TABLE = SET_TO veglenkesekvensid = @Value(_stedfestingsplitt{1})
    -> AttributeCreator_2
AttributeCreator_2
    ATTR_TABLE:
      SET_TO startposisjon = @Value(_posisjoner{0})
      SET_TO sluttposisjon = @Value(_posisjoner{1})
    -> StringReplacer
StringReplacer
    CASE = NO
    FIND_TEXT = #
    NO_MATCH = _FME_NO_OP_
    REGEXP = NO
    REPLACE_TEXT = ,
    SRC_ATTRS = Feltoversikt i veglenkeretning
    -> AttributeManager
AttributeManager
    ATTR_TABLE:
      REMOVE objekttype
      REMOVE startdato
      REMOVE sluttdato
      REMOVE vegsystemreferanser
      REMOVE stedfestinger
      REMOVE stedfesting_detaljer
      REMOVE strekningslengde
      REMOVE Feltoversikt i metreringsretning
      REMOVE fid
      REMOVE _stedfestinger
      REMOVE _element_index
      REMOVE _stedfestingsplitt{}
      REMOVE _posisjoner{}
    -> Counter_2
Counter_2
    CNT_ATTR = _countFelt
    DOMAIN = counter
    SCOPE = Global
    START = 0
    -> InlineQuerier [feltstr]
Note: LEFT JOIN med konnekteringslenker som venstre mengde
InlineQuerier
    QUERY_DEF:
      leftjoin,SELECT * FROM konnekteringslenker
      LEFT JOIN feltstr ON
      feltstr.veglenkesekvensid = konnekteringslenker.veglenkesekvensid AND
      feltstr.startposisjon < konnekteringslenker.sluttposisjon AND
      feltstr.sluttposisjon > konnekteringslenker.startposisjon,FIRST
    QUERY_SCHEMA = leftjoin,veglenkesekvensid,integer,startposisjon,double,sluttposisjon,double,referanse,text,type,text,typeVeg,text,feltoversikt,text,vref,text,vegkategori,text,nummer,double,trafikantgruppe,text,konnekteringslenker.fme_feature_content,fme_feature_content,nvdbId,integer,versjon,integer,"Feltoversikt i veglenkeretning",text,feltstr.fme_feature_content,fme_feature_content
    TABLE_DEF = konnekteringslenker,veglenkesekvensid,integer,startposisjon,double,sluttposisjon,double,referanse,text,type,text,typeVeg,text,feltoversikt,text,vref,text,vegkategori,text,nummer,double,trafikantgruppe,text,feltstr,startposisjon,integer,sluttposisjon,double,veglenkesekvensid,double,nvdbId,integer,versjon,integer,"Feltoversikt i veglenkeretning",text
    leftjoin -> DuplicateFilter_3
DuplicateFilter_3
    INPUT_ORDERED_CHOICE = No
    KEYATTR = _countFelt _count
    UNIQUE -> TestFilter_2
TestFilter_2
    DEFAULT_VALUE = <UNFILTERED>
    PASSED_TEST_GROUP_OUTPUT = FIRST
    TEST_LIST = "BOOL_OP,OR,COMPOSITE_TEST,""""""1"""""",TEST_CLAUSE,TEST _countFelt ATTRIBUTE_HAS_A_VALUE """,_countFelt ATTRIBUTE_HAS_A_VALUE
    _countFelt ATTRIBUTE_HAS_A_VALUE -> AttributeSplitter_4
    <UNFILTERED> -> AttributeCreator_5
AttributeSplitter_4
    ATTR_NAME = feltoversikt
    DELIMITER = ,
    DROP_EMPTY_PARTS = No
    LIST_NAME = _felt
    TRIM_OPTION = Both
    -> ListElementCounter
ListElementCounter
    CNT_ATTR = antallFelt
    LIST_NAME = _felt{}
    -> AttributeKeeper_2
AttributeKeeper_2
    CREATE_BULK_MODE_FEATURES = NO
    KEEP_ATTRS = antallFelt,sluttposisjon,startposisjon,type,typeVeg,veglenkesekvensid,vref,nummer,vegkategori
    -> Clipper [CANDIDATE]
Clipper
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> LengthCalculator
LengthCalculator
    DIM = 2
    LEN_ATTR = _length
    MULT = 1
    -> ExpressionEvaluator
ExpressionEvaluator
    ACTION = Create New Attribute
    EXPRESSION = (1+@Value(_length))*@Value(antallFelt)/1000
    VAL_ATTR = feltlengde
    -> AttributeRenamer
AttributeRenamer
    ATTR_TABLE = RENAME_SET_DEFAULT navn > fylkesnavn
    MISSING_INPUT_ATTRS = REMOVE
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(typeVeg) = Bilferje",Bilferje
    <UNFILTERED> -> StatisticsCalculator
    Bilferje -> StatisticsCalculator_4
StatisticsCalculator_4
    CALCULATION_MODE = NUMERIC
    FEAT_STATS = feltlengde,NUMERIC_MODE,,,,SUM,,,,,,,,,
    GROUP_BY = fylkesnavn fylkesnummer typeVeg
    SUMMARY -> AttributeRenamer_4
AttributeRenamer_4
    ATTR_TABLE = RENAME_SET_DEFAULT feltlengde.sum > feltlengde i km
    MISSING_INPUT_ATTRS = REMOVE
    -> Bilferje feltlengde 2019_07_01 (writer XLSXW_1)
    -> StatisticsCalculator_4_Summary
StatisticsCalculator_4_Summary: Inspector
Bilferje feltlengde 2019_07_01 (writer XLSXW_1)
    attributes: fylkesnavn string(20), fylkesnummer string(20), typeVeg string(20), feltlengde i km number(20)
StatisticsCalculator
    CALCULATION_MODE = NUMERIC
    FEAT_STATS = feltlengde,NUMERIC_MODE,,,,SUM,,,,,,,,,
    GROUP_BY = fylkesnavn fylkesnummer
    SUMMARY -> AttributeRenamer_2
AttributeRenamer_2
    ATTR_TABLE = RENAME_SET_DEFAULT feltlengde.sum > feltlengde i km
    MISSING_INPUT_ATTRS = REMOVE
    -> feltlengder per 2019_07_01 (writer XLSXW_1)
feltlengder per 2019_07_01 (writer XLSXW_1)
    attributes: fylkesnavn string(20), fylkesnummer string(20), feltlengde i km number(20)
AttributeCreator_3 [off]
    ATTR_TABLE = SET_TO analyse =
    -> utenFeltkobling (writer OGCGEOPACKAGE_3)
utenFeltkobling (writer OGCGEOPACKAGE_3) [off]
    attributes: analyse text(200)

Bookmark: Påfører feltinformasjon fra nabolenken
AttributeCreator_4
    ATTR_TABLE:
      SET_TO startpos_tekst = tekst@Value(startposisjon)
      SET_TO sluttpos_tekst = tekst@Value(sluttposisjon)
    -> FeatureMerger [SUPPLIER]
    -> FeatureMerger_2 [SUPPLIER]
AttributeCreator_5
    ATTR_TABLE:
      SET_TO startpos_tekst = tekst@Value(startposisjon)
      SET_TO sluttpos_tekst = tekst@Value(sluttposisjon)
    -> FeatureMerger [REQUESTOR]
    -> FeatureMerger_2 [REQUESTOR]
FeatureMerger_2
    ATTR_ACCUM_MODE = Prefix Supplier
    IGNORE_NULLS = No
    JOIN_KEYS = @Value(veglenkesekvensid) @Value(veglenkesekvensid) AUTO @Value(sluttpos_tekst) @Value(startpos_tekst) AUTO
    MERGE_TYPE = Attributes Only
    PROCESS_DUPS = NO
    REJECT_NULL_MISSING_KEYS = No
    SUPPLIERS_FIRST = No
    SUPPLIER_PREFIX = sup_
    MERGED -> DuplicateFilter_4
FeatureMerger
    ATTR_ACCUM_MODE = Prefix Supplier
    IGNORE_NULLS = No
    JOIN_KEYS = @Value(veglenkesekvensid) @Value(veglenkesekvensid) AUTO @Value(startpos_tekst) @Value(sluttpos_tekst) AUTO
    MERGE_TYPE = Attributes Only
    PROCESS_DUPS = NO
    REJECT_NULL_MISSING_KEYS = No
    SUPPLIERS_FIRST = No
    SUPPLIER_PREFIX = sup_
    MERGED -> DuplicateFilter_4
DuplicateFilter_4
    INPUT_ORDERED_CHOICE = No
    KEYATTR = _count
    UNIQUE -> AttributeCreator_6
Note: Noen få konnekteringslenker gjenstår uten treff (ingen overlapp mot 616 feltstrekning), disse får påført kjørefelt fra tilstøtende vegsegment
AttributeCreator_6
    ATTR_TABLE = SET_TO feltoversikt = @Value(sup_feltoversikt)
    -> AttributeSplitter_4
